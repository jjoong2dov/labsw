module labsw-ops {
  yang-version 1.1;
  namespace "urn:example:labsw-ops";
  prefix lops;

  import ietf-netconf-acm {
    prefix nacm;
  }

  organization
    "labsw (example code for the book)";
  description
    "Backup and restore of the configuration labswd owns
     (labsw-switch and labsw-route in running).

     A backup is a JSON file on the device. Restore replaces both
     modules in running in one transaction: if the agent cannot apply
     the backup to the bridge or FRR, running and the device stay as
     they were.

     Both RPCs are nacm:default-deny-all. NACM lets any user execute
     an RPC unless a rule says otherwise, and restore writes running
     through the agent's own session, where NACM does not look: a
     user without write access could otherwise change running by
     restoring a backup.";

  revision 2026-10-27 {
    description
      "Initial revision.";
  }

  typedef backup-name {
    type string {
      length "1..32";
      pattern '[A-Za-z0-9_-]+';
    }
    description
      "File name without directory and extension; no '/' or '.', so
       a name cannot point outside the backup directory.";
  }

  rpc backup {
    nacm:default-deny-all;
    description
      "Save running of labsw-switch and labsw-route. An existing
       backup of the same name is replaced only when the new file is
       completely written (write a new file, then rename).";
    input {
      leaf name {
        type backup-name;
        mandatory true;
      }
    }
    output {
      leaf bytes {
        type uint64;
      }
    }
  }

  rpc restore {
    nacm:default-deny-all;
    description
      "Replace running of labsw-switch and labsw-route with a backup.";
    input {
      leaf name {
        type backup-name;
        mandatory true;
      }
    }
  }
}
